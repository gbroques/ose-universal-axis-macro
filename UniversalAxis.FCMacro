import FreeCAD as App
import FreeCADGui as Gui
from universal_axis import create_universal_axis


def main():
    document = App.newDocument('Universal Axis')
    universal_axis = create_universal_axis(document, 'UniversalAxis')
    document.recompute()

    # Re-center view
    Gui.SendMsgToActiveView('ViewFit')


if __name__ == '__main__':
    main()
